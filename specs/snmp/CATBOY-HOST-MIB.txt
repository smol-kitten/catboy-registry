-- GENERATED by catboy-registry tools/gen.py from templates/snmp/CATBOY-HOST-MIB.txt.tmpl - do not edit
CATBOY-HOST-MIB DEFINITIONS ::= BEGIN

IMPORTS
    MODULE-IDENTITY, OBJECT-TYPE, Unsigned32, Integer32, Gauge32
        FROM SNMPv2-SMI
    DisplayString, TruthValue
        FROM SNMPv2-TC
    MODULE-COMPLIANCE, OBJECT-GROUP
        FROM SNMPv2-CONF
    catboySnmp
        FROM CATBOY-SMI;

catboyHostMIB MODULE-IDENTITY
    LAST-UPDATED "202610070000Z"
    ORGANIZATION "catboy.systems"
    CONTACT-INFO "Marc Schneider, hostmaster@catboy.systems"
    DESCRIPTION  "Security and health facts of a host running catboy-agent,
                 collected by the agent's hostsec collectors and served by the
                 agent as an AgentX subagent (RFC 2741) of the host's SNMP
                 master agent. Read-only; SNMPv3 authPriv only.

                 Every collector runs on its own interval, only reads, and
                 fails on its own; its state is in catboyHostCollTable. When a
                 run fails, the objects of that collector keep the values of
                 the last successful run and catboyHostCollState shows the
                 failure. Before the first successful run since the agent
                 started, an object holds its unknown value: 4294967295 for
                 counts, ages, durations, the sysctl score and pressure values,
                 -2147483648 for temperatures, zero-length for strings, the
                 unknown member for enumerations that have one, false(2) for
                 truth values, and no rows for tables. The derived objects
                 (catboyHostDerived) are always computed; catboyHostHealthScore
                 has no unknown value and is 100 while no reason applies.

                 An age is the number of seconds from the event to the moment
                 the agent answers the request, so it grows between collector
                 runs. Every table has a bounded index and a stated maximum
                 number of rows; a count scalar next to the table holds the
                 full number when there are more.

                 This module has no notifications: alerting is done by the
                 poller from the derived objects (catboyHostDerived)."
    REVISION     "202610070000Z"
    DESCRIPTION  "Published objects never change meaning. The 202610020000Z
                 description changes of catboyHostSysctlScore,
                 catboyHostSysctlDeviations, catboyHostSysctlDevEntry and
                 catboyHostSysctlDevExpected are reverted: those objects
                 and the whole catboyHostSysctlDevTable keep their first
                 meaning and are deprecated. Their replacements, with the
                 equal-or-stricter rule and the docker0 forwarding rule,
                 are catboyHostSysctlV2Score, catboyHostSysctlV2Deviations
                 and catboyHostSysctlV2DevTable (catboyHostSysctl 4..6).
                 New reason code sysctlScoreLowV2(11). catboyHostSysctlGroup
                 and catboyHostCompliance are deprecated; new
                 catboyHostSysctlV2Group and catboyHostComplianceV2."
    REVISION     "202610020000Z"
    DESCRIPTION  "catboyHostSysctlScore, catboyHostSysctlDeviations,
                 catboyHostSysctlDevEntry and catboyHostSysctlDevExpected: a
                 running value that is stricter than the expected value
                 complies (for example kernel.kptr_restrict 2 where 1 is
                 expected), as the agent implements the checklist.
                 catboyHostSysctlScore: IPv4 forwarding is also expected on
                 hosts with a docker0 bridge, not on routing roles only. No
                 change to any OID or SYNTAX."
    REVISION     "202610010000Z"
    DESCRIPTION  "Initial version (rendered from the catboy-registry template)."
    ::= { catboySnmp 6 }

-- catboyHostNotifications (0) is reserved for notifications.
catboyHostObjects     OBJECT IDENTIFIER ::= { catboyHostMIB 1 }
catboyHostConformance OBJECT IDENTIFIER ::= { catboyHostMIB 2 }

-- One subtree per collector. Subtree n+1 holds the objects of collector
-- index n of catboyHostCollTable; catboyHostDerived (11) holds the flags
-- computed from all collectors.
catboyHostFirewall OBJECT IDENTIFIER ::= { catboyHostObjects 2 }
catboyHostApt      OBJECT IDENTIFIER ::= { catboyHostObjects 3 }
catboyHostReboot   OBJECT IDENTIFIER ::= { catboyHostObjects 4 }
catboyHostSysctl   OBJECT IDENTIFIER ::= { catboyHostObjects 5 }
catboyHostJournal  OBJECT IDENTIFIER ::= { catboyHostObjects 6 }
catboyHostUnits    OBJECT IDENTIFIER ::= { catboyHostObjects 7 }
catboyHostDns      OBJECT IDENTIFIER ::= { catboyHostObjects 8 }
catboyHostSshd     OBJECT IDENTIFIER ::= { catboyHostObjects 9 }
catboyHostPressure OBJECT IDENTIFIER ::= { catboyHostObjects 10 }
catboyHostDerived  OBJECT IDENTIFIER ::= { catboyHostObjects 11 }

-- Collector status

catboyHostCollTable OBJECT-TYPE
    SYNTAX      SEQUENCE OF CatboyHostCollEntry
    MAX-ACCESS  not-accessible
    STATUS      current
    DESCRIPTION "One row per hostsec collector of the agent, always present
                 while the agent runs. At most 32 rows; this revision defines
                 9."
    ::= { catboyHostObjects 1 }

catboyHostCollEntry OBJECT-TYPE
    SYNTAX      CatboyHostCollEntry
    MAX-ACCESS  not-accessible
    STATUS      current
    DESCRIPTION "One collector."
    INDEX       { catboyHostCollIndex }
    ::= { catboyHostCollTable 1 }

CatboyHostCollEntry ::= SEQUENCE {
    catboyHostCollIndex     Unsigned32,
    catboyHostCollName      DisplayString,
    catboyHostCollState     INTEGER,
    catboyHostCollLastOkAge Unsigned32,
    catboyHostCollError     DisplayString
}

catboyHostCollIndex OBJECT-TYPE
    SYNTAX      Unsigned32 (1..32)
    MAX-ACCESS  not-accessible
    STATUS      current
    DESCRIPTION "Fixed collector number, never reassigned: firewall(1), apt(2),
                 reboot(3), sysctl(4), journal(5), units(6), dns(7), sshd(8),
                 psi(9). The objects of collector n are in subtree n+1 of
                 catboyHostObjects."
    ::= { catboyHostCollEntry 1 }

catboyHostCollName OBJECT-TYPE
    SYNTAX      DisplayString (SIZE (1..16))
    MAX-ACCESS  read-only
    STATUS      current
    DESCRIPTION "Collector name, one of firewall, apt, reboot, sysctl, journal,
                 units, dns, sshd, psi; fixed for each catboyHostCollIndex."
    ::= { catboyHostCollEntry 2 }

catboyHostCollState OBJECT-TYPE
    SYNTAX      INTEGER { ok(1), error(2), timeout(3), pending(4),
                          unsupported(5) }
    MAX-ACCESS  read-only
    STATUS      current
    DESCRIPTION "Result of the most recent run of the collector: ok(1) it
                 succeeded; error(2) it failed (the reason is in
                 catboyHostCollError); timeout(3) a query exceeded its time
                 limit; pending(4) it has not completed a run since the agent
                 started; unsupported(5) the host lacks what the collector
                 reads (for example no apt on the host). With error(2) or
                 timeout(3) the collector's objects keep the values of its last
                 successful run. Updated at the end of every run."
    ::= { catboyHostCollEntry 3 }

catboyHostCollLastOkAge OBJECT-TYPE
    SYNTAX      Unsigned32
    UNITS       "seconds"
    MAX-ACCESS  read-only
    STATUS      current
    DESCRIPTION "Seconds since the collector last completed a successful run
                 (an age, not a time of day; the agent computes it when it
                 answers). 4294967295 if no run has succeeded since the agent
                 started."
    ::= { catboyHostCollEntry 4 }

catboyHostCollError OBJECT-TYPE
    SYNTAX      DisplayString (SIZE (0..200))
    MAX-ACCESS  read-only
    STATUS      current
    DESCRIPTION "Error message of the most recent failed or timed-out run,
                 truncated to 200 octets; octets outside printable ASCII are
                 replaced by '?'. Diagnostic text only: consumers decide on
                 catboyHostCollState. Zero-length while catboyHostCollState is
                 ok(1), pending(4) or unsupported(5)."
    ::= { catboyHostCollEntry 5 }

-- Firewall (collector 1, every 5 minutes)

catboyHostFwBackend OBJECT-TYPE
    SYNTAX      INTEGER { none(1), iptables(2), nftables(3), ufw(4),
                          firewalld(5), unknown(6) }
    MAX-ACCESS  read-only
    STATUS      current
    DESCRIPTION "The packet filter that manages the host's input filtering, in
                 the host network namespace: firewalld(5) or ufw(4) when that
                 manager is active; else nftables(3) for a native nftables
                 ruleset; else iptables(2) for rules made with iptables (legacy
                 or the nftables-based iptables front end); none(1) when no
                 filter rules are loaded. From the managers' service state and
                 the loaded rulesets, every 5 minutes. unknown(6) before the
                 first successful run."
    ::= { catboyHostFirewall 1 }

catboyHostFwActive OBJECT-TYPE
    SYNTAX      TruthValue
    MAX-ACCESS  read-only
    STATUS      current
    DESCRIPTION "true(1) if a ruleset with a base chain on the input hook is
                 loaded and, for ufw(4) and firewalld(5), the manager service
                 is active; false(2) otherwise. Every 5 minutes. false(2)
                 before the first successful run."
    ::= { catboyHostFirewall 2 }

catboyHostFwRules OBJECT-TYPE
    SYNTAX      Gauge32
    UNITS       "rules"
    MAX-ACCESS  read-only
    STATUS      current
    DESCRIPTION "Number of rules in the loaded rulesets, over all tables and
                 address families (nftables rules, or iptables and ip6tables
                 rules). Every 5 minutes. 4294967295 before the first
                 successful run."
    ::= { catboyHostFirewall 3 }

catboyHostFwInputPolicy OBJECT-TYPE
    SYNTAX      INTEGER { accept(1), drop(2), reject(3), noChain(4),
                          unknown(5) }
    MAX-ACCESS  read-only
    STATUS      current
    DESCRIPTION "What the input filter chain does with a packet that no rule
                 matched: the policy of the base chain on the input hook,
                 except drop(2) or reject(3) when the last rule of that chain
                 drops or rejects unconditionally. noChain(4) if there is no
                 base chain on the input hook (packets are accepted). If IPv4
                 and IPv6 differ, the more permissive value. Every 5 minutes.
                 unknown(5) before the first successful run."
    ::= { catboyHostFirewall 4 }

catboyHostFwGaps OBJECT-TYPE
    SYNTAX      Gauge32
    UNITS       "sockets"
    MAX-ACCESS  read-only
    STATUS      current
    DESCRIPTION "Number of listening TCP and UDP sockets on a non-loopback
                 address for which the input chain has no accept rule that
                 matches their protocol and port (a source restriction still
                 counts as a match). Such a socket is reachable only through
                 an accept policy, or it is blocked and unused. From the
                 kernel socket tables and the loaded rulesets, every 5
                 minutes. 4294967295 before the first successful run."
    ::= { catboyHostFirewall 5 }

catboyHostFwGapTable OBJECT-TYPE
    SYNTAX      SEQUENCE OF CatboyHostFwGapEntry
    MAX-ACCESS  not-accessible
    STATUS      current
    DESCRIPTION "The sockets counted in catboyHostFwGaps, sorted by protocol,
                 then port. At most 32 rows; catboyHostFwGaps holds the full
                 count."
    ::= { catboyHostFirewall 6 }

catboyHostFwGapEntry OBJECT-TYPE
    SYNTAX      CatboyHostFwGapEntry
    MAX-ACCESS  not-accessible
    STATUS      current
    DESCRIPTION "One listening socket without a matching accept rule."
    INDEX       { catboyHostFwGapIndex }
    ::= { catboyHostFwGapTable 1 }

CatboyHostFwGapEntry ::= SEQUENCE {
    catboyHostFwGapIndex   Unsigned32,
    catboyHostFwGapProto   INTEGER,
    catboyHostFwGapPort    Unsigned32,
    catboyHostFwGapProcess DisplayString
}

catboyHostFwGapIndex OBJECT-TYPE
    SYNTAX      Unsigned32 (1..32)
    MAX-ACCESS  not-accessible
    STATUS      current
    DESCRIPTION "Row index: the position of the socket in the sorted list. It
                 changes when a socket is added or removed. Consumers key on
                 catboyHostFwGapProto and catboyHostFwGapPort."
    ::= { catboyHostFwGapEntry 1 }

catboyHostFwGapProto OBJECT-TYPE
    SYNTAX      INTEGER { tcp(1), udp(2), tcp6(3), udp6(4) }
    MAX-ACCESS  read-only
    STATUS      current
    DESCRIPTION "Transport protocol and address family of the socket."
    ::= { catboyHostFwGapEntry 2 }

catboyHostFwGapPort OBJECT-TYPE
    SYNTAX      Unsigned32 (1..65535)
    MAX-ACCESS  read-only
    STATUS      current
    DESCRIPTION "Local port of the socket."
    ::= { catboyHostFwGapEntry 3 }

catboyHostFwGapProcess OBJECT-TYPE
    SYNTAX      DisplayString (SIZE (0..16))
    MAX-ACCESS  read-only
    STATUS      current
    DESCRIPTION "Command name (comm) of the process that owns the socket.
                 Zero-length if the owner could not be found."
    ::= { catboyHostFwGapEntry 4 }

-- apt and unattended-upgrades (collector 2)

catboyHostAptUpdateAge OBJECT-TYPE
    SYNTAX      Unsigned32
    UNITS       "seconds"
    MAX-ACCESS  read-only
    STATUS      current
    DESCRIPTION "Seconds since the package lists were last refreshed (apt
                 update): the newer of the modification time of the apt lists
                 directory and the APT::Periodic update-success stamp. Every
                 minute. 4294967295 if neither exists or before the first
                 successful run."
    ::= { catboyHostApt 1 }

catboyHostAptUpgradable OBJECT-TYPE
    SYNTAX      Gauge32
    UNITS       "packages"
    MAX-ACCESS  read-only
    STATUS      current
    DESCRIPTION "Packages that a full upgrade would install or upgrade, from
                 an apt simulation (apt-get -s dist-upgrade; takes no lock)
                 over the current package lists. Every 30 minutes. 4294967295
                 before the first successful simulation."
    ::= { catboyHostApt 2 }

catboyHostAptSecUpgradable OBJECT-TYPE
    SYNTAX      Gauge32
    UNITS       "packages"
    MAX-ACCESS  read-only
    STATUS      current
    DESCRIPTION "The part of catboyHostAptUpgradable whose candidate version
                 comes from the distribution's security archive (origin or
                 suite of the Debian or Ubuntu security repository). Every 30
                 minutes. 4294967295 before the first successful simulation."
    ::= { catboyHostApt 3 }

catboyHostUuInstalled OBJECT-TYPE
    SYNTAX      TruthValue
    MAX-ACCESS  read-only
    STATUS      current
    DESCRIPTION "true(1) if the unattended-upgrades package is installed
                 (dpkg status), false(2) otherwise. Every minute. false(2)
                 before the first successful run."
    ::= { catboyHostApt 4 }

catboyHostUuEnabled OBJECT-TYPE
    SYNTAX      TruthValue
    MAX-ACCESS  read-only
    STATUS      current
    DESCRIPTION "true(1) if the effective apt configuration sets
                 APT::Periodic::Unattended-Upgrade to a non-zero value,
                 false(2) otherwise. Every minute. false(2) before the first
                 successful run."
    ::= { catboyHostApt 5 }

catboyHostUuSecurity OBJECT-TYPE
    SYNTAX      TruthValue
    MAX-ACCESS  read-only
    STATUS      current
    DESCRIPTION "true(1) if the origins that unattended-upgrades may install
                 from (Unattended-Upgrade::Origins-Pattern or Allowed-Origins
                 in the effective apt configuration) include the
                 distribution's security archive, false(2) otherwise. Every
                 minute. false(2) before the first successful run."
    ::= { catboyHostApt 6 }

catboyHostUuLastRunAge OBJECT-TYPE
    SYNTAX      Unsigned32
    UNITS       "seconds"
    MAX-ACCESS  read-only
    STATUS      current
    DESCRIPTION "Seconds since the last unattended-upgrades run ended, from
                 its log file. Every minute. 4294967295 if the log records no
                 run or before the first successful run."
    ::= { catboyHostApt 7 }

catboyHostUuLastResult OBJECT-TYPE
    SYNTAX      INTEGER { ok(1), failed(2), none(3), running(4) }
    MAX-ACCESS  read-only
    STATUS      current
    DESCRIPTION "Result of the last unattended-upgrades run, from its log
                 file: ok(1) it finished without error (also with nothing to
                 install), failed(2) it logged an error, none(3) the log
                 records no run or the result could not be read, running(4) a
                 run is in progress. Every minute. none(3) before the first
                 successful run."
    ::= { catboyHostApt 8 }

catboyHostKernelRunning OBJECT-TYPE
    SYNTAX      DisplayString (SIZE (0..64))
    MAX-ACCESS  read-only
    STATUS      current
    DESCRIPTION "Release of the running kernel (uname -r). Every minute.
                 Zero-length before the first successful run."
    ::= { catboyHostApt 9 }

catboyHostKernelNewest OBJECT-TYPE
    SYNTAX      DisplayString (SIZE (0..64))
    MAX-ACCESS  read-only
    STATUS      current
    DESCRIPTION "Release of the newest installed kernel: the highest of the
                 kernel images in /boot, compared as Debian package versions,
                 in the form uname -r prints. Every minute. Zero-length if
                 the host has no kernel image of its own (a container) or
                 before the first successful run."
    ::= { catboyHostApt 10 }

catboyHostKernelOutdated OBJECT-TYPE
    SYNTAX      TruthValue
    MAX-ACCESS  read-only
    STATUS      current
    DESCRIPTION "true(1) if catboyHostKernelNewest is not zero-length and
                 differs from catboyHostKernelRunning (a newer kernel waits
                 for a reboot), false(2) otherwise. Every minute. false(2)
                 before the first successful run."
    ::= { catboyHostApt 11 }

-- Reboot (collector 3, every minute)

catboyHostRebootRequired OBJECT-TYPE
    SYNTAX      TruthValue
    MAX-ACCESS  read-only
    STATUS      current
    DESCRIPTION "true(1) if /var/run/reboot-required exists, false(2)
                 otherwise. Every minute. false(2) before the first successful
                 run."
    ::= { catboyHostReboot 1 }

catboyHostRebootPkgs OBJECT-TYPE
    SYNTAX      Gauge32
    UNITS       "packages"
    MAX-ACCESS  read-only
    STATUS      current
    DESCRIPTION "Number of distinct packages listed in
                 /var/run/reboot-required.pkgs (the packages that asked for
                 the reboot); 0 if the file does not exist. Every minute.
                 4294967295 before the first successful run."
    ::= { catboyHostReboot 2 }

catboyHostUptime OBJECT-TYPE
    SYNTAX      Unsigned32
    UNITS       "seconds"
    MAX-ACCESS  read-only
    STATUS      current
    DESCRIPTION "Seconds since the host (or, in a container, the container)
                 booted, from /proc/uptime. Every minute. 4294967295 before
                 the first successful run."
    ::= { catboyHostReboot 3 }

-- sysctl hardening (collector 4, every 10 minutes)
-- .1-.3: first revision, DEPRECATED (meaning kept as published); .4-.6: the V2 replacements.

catboyHostSysctlScore OBJECT-TYPE
    SYNTAX      Unsigned32 (0..100 | 4294967295)
    UNITS       "percent"
    MAX-ACCESS  read-only
    STATUS      deprecated
    DESCRIPTION "Deprecated in 202610070000Z: replaced by
                 catboyHostSysctlV2Score, which counts a stricter value as
                 compliant. Original meaning: Share of the agent's sysctl checklist whose running value
                 equals the expected value for the host's fleet role, rounded
                 down; 100 means no deviation. The checklist is fixed in the
                 agent (at most 32 keys): kernel pointer and dmesg
                 restriction, ptrace scope, unprivileged BPF and BPF JIT
                 hardening, address space randomization, protected hard
                 links, symbolic links, FIFOs and regular files, reverse path
                 filtering, ICMP redirects (accept and send), source routing,
                 martian logging and IPv4 forwarding. Expected values depend
                 on catboyAgentFleetRole (for example IPv4 forwarding is
                 expected on routing roles only). From /proc/sys, every 10
                 minutes. 4294967295 before the first successful run."
    ::= { catboyHostSysctl 1 }

catboyHostSysctlDeviations OBJECT-TYPE
    SYNTAX      Gauge32
    UNITS       "keys"
    MAX-ACCESS  read-only
    STATUS      deprecated
    DESCRIPTION "Deprecated in 202610070000Z: replaced by
                 catboyHostSysctlV2Deviations, which counts a stricter value as
                 compliant. Original meaning: Number of checklist keys whose running value differs from
                 the expected value, including keys the running kernel does
                 not have. Every 10 minutes. 4294967295 before the first
                 successful run."
    ::= { catboyHostSysctl 2 }

catboyHostSysctlDevTable OBJECT-TYPE
    SYNTAX      SEQUENCE OF CatboyHostSysctlDevEntry
    MAX-ACCESS  not-accessible
    STATUS      deprecated
    DESCRIPTION "Deprecated in 202610070000Z: replaced by
                 catboyHostSysctlV2DevTable, which counts a stricter value as
                 compliant. Original meaning: The keys counted in catboyHostSysctlDeviations, sorted by
                 key. At most 32 rows (the checklist size limit), so the table
                 always holds every deviation."
    ::= { catboyHostSysctl 3 }

catboyHostSysctlDevEntry OBJECT-TYPE
    SYNTAX      CatboyHostSysctlDevEntry
    MAX-ACCESS  not-accessible
    STATUS      deprecated
    DESCRIPTION "Deprecated in 202610070000Z: replaced by
                 catboyHostSysctlV2DevEntry, which counts a stricter value as
                 compliant. Original meaning: One sysctl key whose value differs from the expected value."
    INDEX       { catboyHostSysctlDevIndex }
    ::= { catboyHostSysctlDevTable 1 }

CatboyHostSysctlDevEntry ::= SEQUENCE {
    catboyHostSysctlDevIndex    Unsigned32,
    catboyHostSysctlDevKey      DisplayString,
    catboyHostSysctlDevExpected DisplayString,
    catboyHostSysctlDevActual   DisplayString
}

catboyHostSysctlDevIndex OBJECT-TYPE
    SYNTAX      Unsigned32 (1..32)
    MAX-ACCESS  not-accessible
    STATUS      deprecated
    DESCRIPTION "Deprecated in 202610070000Z: replaced by
                 catboyHostSysctlV2DevIndex, which counts a stricter value as
                 compliant. Original meaning: Row index: the position of the key in the sorted list. It
                 changes when a deviation is added or removed. Consumers key
                 on catboyHostSysctlDevKey."
    ::= { catboyHostSysctlDevEntry 1 }

catboyHostSysctlDevKey OBJECT-TYPE
    SYNTAX      DisplayString (SIZE (1..64))
    MAX-ACCESS  read-only
    STATUS      deprecated
    DESCRIPTION "Deprecated in 202610070000Z: replaced by
                 catboyHostSysctlV2DevKey, which counts a stricter value as
                 compliant. Original meaning: The sysctl key in dotted form (for example
                 kernel.kptr_restrict)."
    ::= { catboyHostSysctlDevEntry 2 }

catboyHostSysctlDevExpected OBJECT-TYPE
    SYNTAX      DisplayString (SIZE (1..32))
    MAX-ACCESS  read-only
    STATUS      deprecated
    DESCRIPTION "Deprecated in 202610070000Z: replaced by
                 catboyHostSysctlV2DevExpected, which counts a stricter value as
                 compliant. Original meaning: The expected value for the host's fleet role, as the decimal
                 text sysctl prints."
    ::= { catboyHostSysctlDevEntry 3 }

catboyHostSysctlDevActual OBJECT-TYPE
    SYNTAX      DisplayString (SIZE (0..32))
    MAX-ACCESS  read-only
    STATUS      deprecated
    DESCRIPTION "Deprecated in 202610070000Z: replaced by
                 catboyHostSysctlV2DevActual, which counts a stricter value as
                 compliant. Original meaning: The running value as the text sysctl prints, with runs of
                 white space collapsed to one space. Zero-length if the
                 running kernel does not have the key."
    ::= { catboyHostSysctlDevEntry 4 }


catboyHostSysctlV2Score OBJECT-TYPE
    SYNTAX      Unsigned32 (0..100 | 4294967295)
    UNITS       "percent"
    MAX-ACCESS  read-only
    STATUS      current
    DESCRIPTION "Share of the agent's sysctl checklist whose running value
                 equals the expected value for the host's fleet role or is
                 stricter than it, rounded down; 100 means no deviation. A
                 stricter value complies: for example kernel.kptr_restrict 2
                 or kernel.unprivileged_bpf_disabled 2 where 1 is expected. The checklist is fixed in the
                 agent (at most 32 keys): kernel pointer and dmesg
                 restriction, ptrace scope, unprivileged BPF and BPF JIT
                 hardening, address space randomization, protected hard
                 links, symbolic links, FIFOs and regular files, reverse path
                 filtering, ICMP redirects (accept and send), source routing,
                 martian logging and IPv4 forwarding. Expected values depend
                 on catboyAgentFleetRole and on the host: IPv4 forwarding is
                 expected on routing roles and on hosts with a docker0
                 bridge (the container engine needs it), and is expected
                 off elsewhere. From /proc/sys, every 10
                 minutes. 4294967295 before the first successful run."
    ::= { catboyHostSysctl 4 }

catboyHostSysctlV2Deviations OBJECT-TYPE
    SYNTAX      Gauge32
    UNITS       "keys"
    MAX-ACCESS  read-only
    STATUS      current
    DESCRIPTION "Number of checklist keys whose running value neither
                 equals the expected value nor is stricter than it, including
                 keys the running kernel does not have. Every 10 minutes. 4294967295 before the first
                 successful run."
    ::= { catboyHostSysctl 5 }

catboyHostSysctlV2DevTable OBJECT-TYPE
    SYNTAX      SEQUENCE OF CatboyHostSysctlV2DevEntry
    MAX-ACCESS  not-accessible
    STATUS      current
    DESCRIPTION "The keys counted in catboyHostSysctlV2Deviations, sorted by
                 key. At most 32 rows (the checklist size limit), so the table
                 always holds every deviation."
    ::= { catboyHostSysctl 6 }

catboyHostSysctlV2DevEntry OBJECT-TYPE
    SYNTAX      CatboyHostSysctlV2DevEntry
    MAX-ACCESS  not-accessible
    STATUS      current
    DESCRIPTION "One sysctl key whose value neither equals the expected
                 value nor is stricter than it."
    INDEX       { catboyHostSysctlV2DevIndex }
    ::= { catboyHostSysctlV2DevTable 1 }

CatboyHostSysctlV2DevEntry ::= SEQUENCE {
    catboyHostSysctlV2DevIndex    Unsigned32,
    catboyHostSysctlV2DevKey      DisplayString,
    catboyHostSysctlV2DevExpected DisplayString,
    catboyHostSysctlV2DevActual   DisplayString
}

catboyHostSysctlV2DevIndex OBJECT-TYPE
    SYNTAX      Unsigned32 (1..32)
    MAX-ACCESS  not-accessible
    STATUS      current
    DESCRIPTION "Row index: the position of the key in the sorted list. It
                 changes when a deviation is added or removed. Consumers key
                 on catboyHostSysctlV2DevKey."
    ::= { catboyHostSysctlV2DevEntry 1 }

catboyHostSysctlV2DevKey OBJECT-TYPE
    SYNTAX      DisplayString (SIZE (1..64))
    MAX-ACCESS  read-only
    STATUS      current
    DESCRIPTION "The sysctl key in dotted form (for example
                 kernel.kptr_restrict)."
    ::= { catboyHostSysctlV2DevEntry 2 }

catboyHostSysctlV2DevExpected OBJECT-TYPE
    SYNTAX      DisplayString (SIZE (1..32))
    MAX-ACCESS  read-only
    STATUS      current
    DESCRIPTION "The expected value for the host's fleet role, as the decimal
                 text sysctl prints: the least strict value that complies."
    ::= { catboyHostSysctlV2DevEntry 3 }

catboyHostSysctlV2DevActual OBJECT-TYPE
    SYNTAX      DisplayString (SIZE (0..32))
    MAX-ACCESS  read-only
    STATUS      current
    DESCRIPTION "The running value as the text sysctl prints, with runs of
                 white space collapsed to one space. Zero-length if the
                 running kernel does not have the key."
    ::= { catboyHostSysctlV2DevEntry 4 }

-- Journal (collector 5; 1 h values every minute, 24 h and 48 h values every
-- 10 minutes; each query is bounded by a start time and a time limit)

catboyHostJournalCrit1h OBJECT-TYPE
    SYNTAX      Gauge32
    UNITS       "messages"
    MAX-ACCESS  read-only
    STATUS      current
    DESCRIPTION "Journal messages of priority emerg, alert or crit (0 to 2)
                 in the last hour, from the system journal. Every minute.
                 4294967295 before the first successful run."
    ::= { catboyHostJournal 1 }

catboyHostJournalCrit24h OBJECT-TYPE
    SYNTAX      Gauge32
    UNITS       "messages"
    MAX-ACCESS  read-only
    STATUS      current
    DESCRIPTION "As catboyHostJournalCrit1h over the last 24 hours. Every 10
                 minutes. 4294967295 before the first successful run."
    ::= { catboyHostJournal 2 }

catboyHostJournalCrit48h OBJECT-TYPE
    SYNTAX      Gauge32
    UNITS       "messages"
    MAX-ACCESS  read-only
    STATUS      current
    DESCRIPTION "As catboyHostJournalCrit1h over the last 48 hours. Every 10
                 minutes. 4294967295 before the first successful run."
    ::= { catboyHostJournal 3 }

catboyHostJournalErr1h OBJECT-TYPE
    SYNTAX      Gauge32
    UNITS       "messages"
    MAX-ACCESS  read-only
    STATUS      current
    DESCRIPTION "Journal messages of priority err (3) only, in the last hour,
                 from the system journal; messages of a higher priority are
                 counted in catboyHostJournalCrit1h, not here. Every minute.
                 4294967295 before the first successful run."
    ::= { catboyHostJournal 4 }

catboyHostJournalErr24h OBJECT-TYPE
    SYNTAX      Gauge32
    UNITS       "messages"
    MAX-ACCESS  read-only
    STATUS      current
    DESCRIPTION "As catboyHostJournalErr1h over the last 24 hours. Every 10
                 minutes. 4294967295 before the first successful run."
    ::= { catboyHostJournal 5 }

catboyHostJournalErr48h OBJECT-TYPE
    SYNTAX      Gauge32
    UNITS       "messages"
    MAX-ACCESS  read-only
    STATUS      current
    DESCRIPTION "As catboyHostJournalErr1h over the last 48 hours. Every 10
                 minutes. 4294967295 before the first successful run."
    ::= { catboyHostJournal 6 }

catboyHostJournalOom24h OBJECT-TYPE
    SYNTAX      Gauge32
    UNITS       "kills"
    MAX-ACCESS  read-only
    STATUS      current
    DESCRIPTION "Processes killed for lack of memory in the last 24 hours:
                 kernel OOM killer kill messages plus systemd-oomd kills, from
                 the journal. Every 10 minutes. 4294967295 before the first
                 successful run."
    ::= { catboyHostJournal 7 }

catboyHostJournalSegv24h OBJECT-TYPE
    SYNTAX      Gauge32
    UNITS       "faults"
    MAX-ACCESS  read-only
    STATUS      current
    DESCRIPTION "Segmentation faults the kernel logged for user processes in
                 the last 24 hours, from the kernel messages in the journal.
                 Every 10 minutes. 4294967295 before the first successful
                 run."
    ::= { catboyHostJournal 8 }

catboyHostJournalCore48h OBJECT-TYPE
    SYNTAX      Gauge32
    UNITS       "coredumps"
    MAX-ACCESS  read-only
    STATUS      current
    DESCRIPTION "Core dumps recorded by systemd-coredump in the last 48 hours
                 (coredumpctl). 0 if systemd-coredump is not installed. Every
                 10 minutes. 4294967295 before the first successful run."
    ::= { catboyHostJournal 9 }

catboyHostKernelTaint OBJECT-TYPE
    SYNTAX      Unsigned32
    MAX-ACCESS  read-only
    STATUS      current
    DESCRIPTION "The kernel taint bit mask from /proc/sys/kernel/tainted, as
                 a number; 0 means not tainted. The bits are those of the
                 kernel documentation (admin-guide/tainted-kernels). Every
                 minute. 4294967295 before the first successful run."
    ::= { catboyHostJournal 10 }

catboyHostCritLineTable OBJECT-TYPE
    SYNTAX      SEQUENCE OF CatboyHostCritLineEntry
    MAX-ACCESS  not-accessible
    STATUS      current
    DESCRIPTION "The newest journal messages of priority emerg, alert or crit
                 in the last 48 hours, newest first. At most 5 rows. Every 10
                 minutes."
    ::= { catboyHostJournal 11 }

catboyHostCritLineEntry OBJECT-TYPE
    SYNTAX      CatboyHostCritLineEntry
    MAX-ACCESS  not-accessible
    STATUS      current
    DESCRIPTION "One journal message."
    INDEX       { catboyHostCritLineIndex }
    ::= { catboyHostCritLineTable 1 }

CatboyHostCritLineEntry ::= SEQUENCE {
    catboyHostCritLineIndex    Unsigned32,
    catboyHostCritLineAge      Unsigned32,
    catboyHostCritLinePriority INTEGER,
    catboyHostCritLineIdent    DisplayString,
    catboyHostCritLineText     DisplayString
}

catboyHostCritLineIndex OBJECT-TYPE
    SYNTAX      Unsigned32 (1..5)
    MAX-ACCESS  not-accessible
    STATUS      current
    DESCRIPTION "Row index: 1 is the newest message. It changes with every
                 new message."
    ::= { catboyHostCritLineEntry 1 }

catboyHostCritLineAge OBJECT-TYPE
    SYNTAX      Unsigned32
    UNITS       "seconds"
    MAX-ACCESS  read-only
    STATUS      current
    DESCRIPTION "Seconds since the message was logged (its realtime journal
                 timestamp)."
    ::= { catboyHostCritLineEntry 2 }

catboyHostCritLinePriority OBJECT-TYPE
    SYNTAX      INTEGER { emerg(1), alert(2), crit(3) }
    MAX-ACCESS  read-only
    STATUS      current
    DESCRIPTION "Syslog priority of the message. The values are the syslog
                 priority plus one."
    ::= { catboyHostCritLineEntry 3 }

catboyHostCritLineIdent OBJECT-TYPE
    SYNTAX      DisplayString (SIZE (0..32))
    MAX-ACCESS  read-only
    STATUS      current
    DESCRIPTION "The syslog identifier of the message (for example kernel),
                 truncated to 32 octets. Zero-length if the message has
                 none."
    ::= { catboyHostCritLineEntry 4 }

catboyHostCritLineText OBJECT-TYPE
    SYNTAX      DisplayString (SIZE (0..200))
    MAX-ACCESS  read-only
    STATUS      current
    DESCRIPTION "The message text, truncated to 200 octets; octets outside
                 printable ASCII are replaced by '?'. Diagnostic text only;
                 the counts are in catboyHostJournalCrit1h and its
                 siblings."
    ::= { catboyHostCritLineEntry 5 }

-- Failed units (collector 6, every minute)

catboyHostUnitsFailed OBJECT-TYPE
    SYNTAX      Gauge32
    UNITS       "units"
    MAX-ACCESS  read-only
    STATUS      current
    DESCRIPTION "Units of the systemd system manager in the failed state.
                 Every minute. 4294967295 before the first successful run."
    ::= { catboyHostUnits 1 }

catboyHostUnitsRestarting OBJECT-TYPE
    SYNTAX      Gauge32
    UNITS       "units"
    MAX-ACCESS  read-only
    STATUS      current
    DESCRIPTION "Units whose automatic restart counter (NRestarts) went up by
                 more than 3 in the last hour, as seen by the agent's
                 samples. Every minute. 4294967295 before the first
                 successful run."
    ::= { catboyHostUnits 2 }

catboyHostTimersOverdue OBJECT-TYPE
    SYNTAX      Gauge32
    UNITS       "timers"
    MAX-ACCESS  read-only
    STATUS      current
    DESCRIPTION "Active systemd timers whose next scheduled elapse is more
                 than 1 hour in the past. Every minute. 4294967295 before the
                 first successful run."
    ::= { catboyHostUnits 3 }

catboyHostFailedTable OBJECT-TYPE
    SYNTAX      SEQUENCE OF CatboyHostFailedEntry
    MAX-ACCESS  not-accessible
    STATUS      current
    DESCRIPTION "The units counted in catboyHostUnitsFailed, sorted by name.
                 At most 32 rows; catboyHostUnitsFailed holds the full
                 count."
    ::= { catboyHostUnits 4 }

catboyHostFailedEntry OBJECT-TYPE
    SYNTAX      CatboyHostFailedEntry
    MAX-ACCESS  not-accessible
    STATUS      current
    DESCRIPTION "One failed unit."
    INDEX       { catboyHostFailedIndex }
    ::= { catboyHostFailedTable 1 }

CatboyHostFailedEntry ::= SEQUENCE {
    catboyHostFailedIndex Unsigned32,
    catboyHostFailedName  DisplayString,
    catboyHostFailedAge   Unsigned32
}

catboyHostFailedIndex OBJECT-TYPE
    SYNTAX      Unsigned32 (1..32)
    MAX-ACCESS  not-accessible
    STATUS      current
    DESCRIPTION "Row index: the position of the unit in the sorted list. It
                 changes when a unit is added or removed. Consumers key on
                 catboyHostFailedName."
    ::= { catboyHostFailedEntry 1 }

catboyHostFailedName OBJECT-TYPE
    SYNTAX      DisplayString (SIZE (1..255))
    MAX-ACCESS  read-only
    STATUS      current
    DESCRIPTION "Full unit name including its type suffix (for example
                 example.service)."
    ::= { catboyHostFailedEntry 2 }

catboyHostFailedAge OBJECT-TYPE
    SYNTAX      Unsigned32
    UNITS       "seconds"
    MAX-ACCESS  read-only
    STATUS      current
    DESCRIPTION "Seconds since the unit entered the failed state (its state
                 change timestamp). 4294967295 if systemd reports no
                 timestamp."
    ::= { catboyHostFailedEntry 3 }

-- DNS (collector 7, every minute)

catboyHostDnsResolvers OBJECT-TYPE
    SYNTAX      Gauge32
    UNITS       "resolvers"
    MAX-ACCESS  read-only
    STATUS      current
    DESCRIPTION "Configured DNS resolvers: the nameserver entries of
                 /etc/resolv.conf or, when it points only at the local
                 systemd-resolved stub, the upstream servers of
                 systemd-resolved. Every minute. 4294967295 before the first
                 successful run."
    ::= { catboyHostDns 1 }

catboyHostDnsFirstIsFleet OBJECT-TYPE
    SYNTAX      TruthValue
    MAX-ACCESS  read-only
    STATUS      current
    DESCRIPTION "true(1) if the first configured resolver is the fleet
                 resolver set in the agent's configuration, false(2) if it is
                 another one, if none is configured, or if the agent has no
                 fleet resolver set. Every minute. false(2) before the first
                 successful run."
    ::= { catboyHostDns 2 }

catboyHostDnsLastMs OBJECT-TYPE
    SYNTAX      Unsigned32
    UNITS       "milliseconds"
    MAX-ACCESS  read-only
    STATUS      current
    DESCRIPTION "Response time of the last probe: one A query per minute for
                 a fixed name set in the agent's configuration, sent to the
                 first configured resolver. 4294967295 if the last probe
                 failed or no probe has run."
    ::= { catboyHostDns 3 }

catboyHostDnsAvg15mMs OBJECT-TYPE
    SYNTAX      Unsigned32
    UNITS       "milliseconds"
    MAX-ACCESS  read-only
    STATUS      current
    DESCRIPTION "Mean response time of the successful probes in the last 15
                 minutes, rounded to the nearest millisecond. 4294967295 if
                 no probe succeeded in that window."
    ::= { catboyHostDns 4 }

catboyHostDnsFail15m OBJECT-TYPE
    SYNTAX      Gauge32
    UNITS       "queries"
    MAX-ACCESS  read-only
    STATUS      current
    DESCRIPTION "Probes in the last 15 minutes that failed: no answer within
                 the agent's query time limit, or a response code other than
                 NOERROR, or no A record in the answer. At most 15 at one
                 probe per minute. 4294967295 before the first probe."
    ::= { catboyHostDns 5 }

-- sshd and local accounts (collector 8; every 10 minutes, the setuid scan
-- every 24 hours)

catboyHostSshRootLogin OBJECT-TYPE
    SYNTAX      INTEGER { yes(1), no(2), prohibitPassword(3),
                          forcedCommandsOnly(4), notInstalled(5),
                          unknown(6) }
    MAX-ACCESS  read-only
    STATUS      current
    DESCRIPTION "The effective PermitRootLogin of sshd outside any Match
                 block, from the configuration sshd -T prints.
                 notInstalled(5) if there is no sshd on the host. Every 10
                 minutes. unknown(6) if the configuration could not be read
                 or before the first successful run. The listen addresses of
                 sshd are deliberately left out of this public module: they
                 are host topology, not a definable count or flag."
    ::= { catboyHostSshd 1 }

catboyHostSshPasswordAuth OBJECT-TYPE
    SYNTAX      TruthValue
    MAX-ACCESS  read-only
    STATUS      current
    DESCRIPTION "true(1) if the effective PasswordAuthentication of sshd
                 outside any Match block is yes, false(2) if it is no or
                 there is no sshd. Every 10 minutes. false(2) before the
                 first successful run."
    ::= { catboyHostSshd 2 }

catboyHostSshAuthFail24h OBJECT-TYPE
    SYNTAX      Gauge32
    UNITS       "attempts"
    MAX-ACCESS  read-only
    STATUS      current
    DESCRIPTION "Failed sshd authentication attempts in the last 24 hours:
                 sshd journal messages that report a failed password or key,
                 or an invalid user. Every 10 minutes. 4294967295 before the
                 first successful run."
    ::= { catboyHostSshd 3 }

catboyHostEmptyPwUsers OBJECT-TYPE
    SYNTAX      Gauge32
    UNITS       "accounts"
    MAX-ACCESS  read-only
    STATUS      current
    DESCRIPTION "Local accounts whose password field in /etc/shadow is
                 empty (login without a password). Locked accounts are not
                 counted. Every 10 minutes. 4294967295 before the first
                 successful run."
    ::= { catboyHostSshd 4 }

catboyHostNopasswdSudo OBJECT-TYPE
    SYNTAX      Gauge32
    UNITS       "entries"
    MAX-ACCESS  read-only
    STATUS      current
    DESCRIPTION "sudoers rules with the NOPASSWD tag in /etc/sudoers and the
                 files it includes. Every 10 minutes. 4294967295 before the
                 first successful run."
    ::= { catboyHostSshd 5 }

catboyHostWwPathDirs OBJECT-TYPE
    SYNTAX      Gauge32
    UNITS       "directories"
    MAX-ACCESS  read-only
    STATUS      current
    DESCRIPTION "Directories in the system default PATH (ENV_PATH and
                 ENV_SUPATH of /etc/login.defs, and PATH in /etc/environment)
                 that any user may write to (mode o+w), after following
                 symbolic links. Every 10 minutes. 4294967295 before the
                 first successful run."
    ::= { catboyHostSshd 6 }

catboyHostSetuidUnpkg OBJECT-TYPE
    SYNTAX      Gauge32
    UNITS       "files"
    MAX-ACCESS  read-only
    STATUS      current
    DESCRIPTION "Regular files with the setuid or setgid bit that no
                 installed package owns (dpkg). Scanned without crossing
                 file system boundaries (find -xdev) over /usr, /bin, /sbin,
                 /lib* and /opt only, every 24 hours. 4294967295 before the
                 first successful scan."
    ::= { catboyHostSshd 7 }

-- Pressure stall information and temperature (collector 9, every minute).
-- PSI values are the avg10, avg60 and avg300 fields of /proc/pressure/*
-- (percent of wall time, two decimals) times 100: UNITS '0.01 percent',
-- range 0..10000, so 1234 means 12.34 percent.

catboyHostPsiAvailable OBJECT-TYPE
    SYNTAX      TruthValue
    MAX-ACCESS  read-only
    STATUS      current
    DESCRIPTION "true(1) if /proc/pressure can be read; false(2) if the
                 kernel has no PSI, PSI is disabled at boot, or the container
                 does not expose it. While false(2) every PSI object of this
                 module is 4294967295. Every minute."
    ::= { catboyHostPressure 1 }

catboyHostPsiCpuSome10 OBJECT-TYPE
    SYNTAX      Unsigned32 (0..10000 | 4294967295)
    UNITS       "0.01 percent"
    MAX-ACCESS  read-only
    STATUS      current
    DESCRIPTION "CPU pressure, some line, avg10 of /proc/pressure/cpu, in
                 hundredths of a percent: the share of the last 10 seconds in
                 which at least one task waited for a CPU. Every minute.
                 4294967295 while PSI is not available or before the first
                 successful run. CPU pressure full is deliberately not
                 exported: at system level the kernel reports it as zero
                 (it has meaning only per cgroup), so only the some line of
                 CPU pressure is served, and load control uses only that."
    ::= { catboyHostPressure 2 }

catboyHostPsiCpuSome60 OBJECT-TYPE
    SYNTAX      Unsigned32 (0..10000 | 4294967295)
    UNITS       "0.01 percent"
    MAX-ACCESS  read-only
    STATUS      current
    DESCRIPTION "As catboyHostPsiCpuSome10 for avg60 (the last 60
                 seconds)."
    ::= { catboyHostPressure 3 }

catboyHostPsiCpuSome300 OBJECT-TYPE
    SYNTAX      Unsigned32 (0..10000 | 4294967295)
    UNITS       "0.01 percent"
    MAX-ACCESS  read-only
    STATUS      current
    DESCRIPTION "As catboyHostPsiCpuSome10 for avg300 (the last 300
                 seconds)."
    ::= { catboyHostPressure 4 }

catboyHostPsiMemSome10 OBJECT-TYPE
    SYNTAX      Unsigned32 (0..10000 | 4294967295)
    UNITS       "0.01 percent"
    MAX-ACCESS  read-only
    STATUS      current
    DESCRIPTION "Memory pressure, some line, avg10 of /proc/pressure/memory,
                 in hundredths of a percent: the share of the last 10
                 seconds in which at least one task stalled on memory.
                 Every minute. 4294967295 while PSI is not available or
                 before the first successful run."
    ::= { catboyHostPressure 5 }

catboyHostPsiMemSome60 OBJECT-TYPE
    SYNTAX      Unsigned32 (0..10000 | 4294967295)
    UNITS       "0.01 percent"
    MAX-ACCESS  read-only
    STATUS      current
    DESCRIPTION "As catboyHostPsiMemSome10 for avg60."
    ::= { catboyHostPressure 6 }

catboyHostPsiMemSome300 OBJECT-TYPE
    SYNTAX      Unsigned32 (0..10000 | 4294967295)
    UNITS       "0.01 percent"
    MAX-ACCESS  read-only
    STATUS      current
    DESCRIPTION "As catboyHostPsiMemSome10 for avg300."
    ::= { catboyHostPressure 7 }

catboyHostPsiMemFull10 OBJECT-TYPE
    SYNTAX      Unsigned32 (0..10000 | 4294967295)
    UNITS       "0.01 percent"
    MAX-ACCESS  read-only
    STATUS      current
    DESCRIPTION "Memory pressure, full line, avg10 of /proc/pressure/memory,
                 in hundredths of a percent: the share of the last 10
                 seconds in which all non-idle tasks stalled on memory at
                 the same time. Every minute. 4294967295 while PSI is not
                 available or before the first successful run."
    ::= { catboyHostPressure 8 }

catboyHostPsiMemFull60 OBJECT-TYPE
    SYNTAX      Unsigned32 (0..10000 | 4294967295)
    UNITS       "0.01 percent"
    MAX-ACCESS  read-only
    STATUS      current
    DESCRIPTION "As catboyHostPsiMemFull10 for avg60."
    ::= { catboyHostPressure 9 }

catboyHostPsiMemFull300 OBJECT-TYPE
    SYNTAX      Unsigned32 (0..10000 | 4294967295)
    UNITS       "0.01 percent"
    MAX-ACCESS  read-only
    STATUS      current
    DESCRIPTION "As catboyHostPsiMemFull10 for avg300."
    ::= { catboyHostPressure 10 }

catboyHostPsiIoSome10 OBJECT-TYPE
    SYNTAX      Unsigned32 (0..10000 | 4294967295)
    UNITS       "0.01 percent"
    MAX-ACCESS  read-only
    STATUS      current
    DESCRIPTION "IO pressure, some line, avg10 of /proc/pressure/io, in
                 hundredths of a percent: the share of the last 10 seconds
                 in which at least one task waited for IO. Every minute.
                 4294967295 while PSI is not available or before the first
                 successful run."
    ::= { catboyHostPressure 11 }

catboyHostPsiIoSome60 OBJECT-TYPE
    SYNTAX      Unsigned32 (0..10000 | 4294967295)
    UNITS       "0.01 percent"
    MAX-ACCESS  read-only
    STATUS      current
    DESCRIPTION "As catboyHostPsiIoSome10 for avg60."
    ::= { catboyHostPressure 12 }

catboyHostPsiIoSome300 OBJECT-TYPE
    SYNTAX      Unsigned32 (0..10000 | 4294967295)
    UNITS       "0.01 percent"
    MAX-ACCESS  read-only
    STATUS      current
    DESCRIPTION "As catboyHostPsiIoSome10 for avg300."
    ::= { catboyHostPressure 13 }

catboyHostPsiIoFull10 OBJECT-TYPE
    SYNTAX      Unsigned32 (0..10000 | 4294967295)
    UNITS       "0.01 percent"
    MAX-ACCESS  read-only
    STATUS      current
    DESCRIPTION "IO pressure, full line, avg10 of /proc/pressure/io, in
                 hundredths of a percent: the share of the last 10 seconds
                 in which all non-idle tasks waited for IO at the same time.
                 Every minute. 4294967295 while PSI is not available or
                 before the first successful run."
    ::= { catboyHostPressure 14 }

catboyHostPsiIoFull60 OBJECT-TYPE
    SYNTAX      Unsigned32 (0..10000 | 4294967295)
    UNITS       "0.01 percent"
    MAX-ACCESS  read-only
    STATUS      current
    DESCRIPTION "As catboyHostPsiIoFull10 for avg60."
    ::= { catboyHostPressure 15 }

catboyHostPsiIoFull300 OBJECT-TYPE
    SYNTAX      Unsigned32 (0..10000 | 4294967295)
    UNITS       "0.01 percent"
    MAX-ACCESS  read-only
    STATUS      current
    DESCRIPTION "As catboyHostPsiIoFull10 for avg300."
    ::= { catboyHostPressure 16 }

catboyHostTempMax OBJECT-TYPE
    SYNTAX      Integer32
    UNITS       "millidegrees Celsius"
    MAX-ACCESS  read-only
    STATUS      current
    DESCRIPTION "Highest temperature over all hwmon temperature inputs
                 (/sys/class/hwmon/*/temp*_input; on AMD processors this
                 includes the k10temp Tctl value), in thousandths of a degree
                 Celsius. Every minute. -2147483648 if the host has no
                 readable sensor (catboyHostTempSensors is 0, as in most
                 containers) or before the first successful run."
    ::= { catboyHostPressure 17 }

catboyHostTempSensors OBJECT-TYPE
    SYNTAX      Gauge32
    UNITS       "sensors"
    MAX-ACCESS  read-only
    STATUS      current
    DESCRIPTION "Number of hwmon temperature inputs that could be read in the
                 last run; 0 if there are none. Every minute. 4294967295
                 before the first successful run."
    ::= { catboyHostPressure 18 }

-- Derived flags (computed every minute from the latest collector values;
-- the thresholds named here are the agent's defaults)

catboyHostNeedsReboot OBJECT-TYPE
    SYNTAX      TruthValue
    MAX-ACCESS  read-only
    STATUS      current
    DESCRIPTION "true(1) if catboyHostRebootRequired or
                 catboyHostKernelOutdated is true, false(2) otherwise. A
                 reboot is never automatic. Every minute."
    ::= { catboyHostDerived 1 }

catboyHostNeedsRebootAge OBJECT-TYPE
    SYNTAX      Unsigned32
    UNITS       "seconds"
    MAX-ACCESS  read-only
    STATUS      current
    DESCRIPTION "Seconds since catboyHostNeedsReboot last became true, from
                 the first-seen time the agent keeps; 0 while it is false.
                 Every minute."
    ::= { catboyHostDerived 2 }

catboyHostSecPending OBJECT-TYPE
    SYNTAX      TruthValue
    MAX-ACCESS  read-only
    STATUS      current
    DESCRIPTION "true(1) if catboyHostAptSecUpgradable is greater than 0 and
                 not unknown, false(2) otherwise. Every minute."
    ::= { catboyHostDerived 3 }

catboyHostSecOverdue OBJECT-TYPE
    SYNTAX      TruthValue
    MAX-ACCESS  read-only
    STATUS      current
    DESCRIPTION "true(1) if catboyHostSecPending has been true without a
                 break for more than 7 days (from the first-seen time the
                 agent keeps), false(2) otherwise. Every minute."
    ::= { catboyHostDerived 4 }

catboyHostNeedsIntervention OBJECT-TYPE
    SYNTAX      TruthValue
    MAX-ACCESS  read-only
    STATUS      current
    DESCRIPTION "true(1) if at least one reason is in catboyHostReasonTable,
                 false(2) if the table is empty. Never true without a reason.
                 Every minute."
    ::= { catboyHostDerived 5 }

catboyHostSeverity OBJECT-TYPE
    SYNTAX      INTEGER { none(1), medium(2), high(3) }
    MAX-ACCESS  read-only
    STATUS      current
    DESCRIPTION "The highest catboyHostReasonSeverity in
                 catboyHostReasonTable; none(1) if the table is empty. high(3)
                 is the only value meant to page. Every minute."
    ::= { catboyHostDerived 6 }

catboyHostHealthScore OBJECT-TYPE
    SYNTAX      Unsigned32 (0..100)
    UNITS       "percent"
    MAX-ACCESS  read-only
    STATUS      current
    DESCRIPTION "Informational health score: 100, minus 25 for each high and
                 10 for each medium reason in catboyHostReasonTable, not
                 below 0. It is always computable and has no unknown value:
                 an empty reason table (also before any collector has run)
                 gives 100. Never meant for paging. Every minute."
    ::= { catboyHostDerived 7 }

catboyHostReasonCount OBJECT-TYPE
    SYNTAX      Gauge32
    UNITS       "reasons"
    MAX-ACCESS  read-only
    STATUS      current
    DESCRIPTION "Number of rows in catboyHostReasonTable. Every minute."
    ::= { catboyHostDerived 8 }

catboyHostReasonTable OBJECT-TYPE
    SYNTAX      SEQUENCE OF CatboyHostReasonEntry
    MAX-ACCESS  not-accessible
    STATUS      current
    DESCRIPTION "The reasons why catboyHostNeedsIntervention is true, one row
                 per reason code that applies, indexed by the code, so a
                 reason keeps its row while other reasons come and go. At
                 most 16 rows (codes are limited to 1..16), so the table
                 always holds every reason. A reason from a collector that
                 is not ok(1) is computed from that collector's last
                 successful values. Every minute."
    ::= { catboyHostDerived 9 }

catboyHostReasonEntry OBJECT-TYPE
    SYNTAX      CatboyHostReasonEntry
    MAX-ACCESS  not-accessible
    STATUS      current
    DESCRIPTION "One reason that applies now."
    INDEX       { catboyHostReasonCode }
    ::= { catboyHostReasonTable 1 }

CatboyHostReasonEntry ::= SEQUENCE {
    catboyHostReasonCode     INTEGER,
    catboyHostReasonSeverity INTEGER,
    catboyHostReasonDetail   DisplayString,
    catboyHostReasonAge      Unsigned32
}

catboyHostReasonCode OBJECT-TYPE
    SYNTAX      INTEGER { failedUnit(1), journalCrit(2), oomKill(3),
                          coredump(4), diskFull(5), securityOverdue(6),
                          firewallMissing(7), dnsFailures(8),
                          sshRootPassword(9), sysctlScoreLow(10),
                          sysctlScoreLowV2(11) }
    MAX-ACCESS  not-accessible
    STATUS      current
    DESCRIPTION "Row index: why intervention is needed. failedUnit(1) a unit
                 has been failed for more than 1 hour; journalCrit(2)
                 catboyHostJournalCrit1h is greater than 0; oomKill(3)
                 catboyHostJournalOom24h is greater than 0; coredump(4) a
                 core dump was recorded in the last 24 hours; diskFull(5)
                 catboyAgentDiskFull is true; securityOverdue(6)
                 catboyHostSecOverdue is true; firewallMissing(7) the host's
                 fleet role is marked exposed and catboyHostFwBackend is
                 none(1) or catboyHostFwActive is false; dnsFailures(8)
                 catboyHostDnsFail15m is 5 or more; sshRootPassword(9)
                 catboyHostSshPasswordAuth is true and catboyHostSshRootLogin
                 is yes(1); sysctlScoreLow(10) catboyHostSysctlScore is below
                 60 (an agent that serves catboyHostSysctlV2Group reports
                 code 11 instead); sysctlScoreLowV2(11)
                 catboyHostSysctlV2Score is below 60. Codes are never reused or renumbered; new codes are
                 added at the end, never above 16."
    ::= { catboyHostReasonEntry 1 }

catboyHostReasonSeverity OBJECT-TYPE
    SYNTAX      INTEGER { medium(2), high(3) }
    MAX-ACCESS  read-only
    STATUS      current
    DESCRIPTION "Severity of the reason, with the values of
                 catboyHostSeverity: high(3) for journalCrit, oomKill,
                 diskFull and firewallMissing; medium(2) for every other
                 code."
    ::= { catboyHostReasonEntry 2 }

catboyHostReasonDetail OBJECT-TYPE
    SYNTAX      DisplayString (SIZE (0..200))
    MAX-ACCESS  read-only
    STATUS      current
    DESCRIPTION "Short detail for a human, truncated to 200 octets, for
                 example the names of the failed units or the count that
                 crossed the threshold. Diagnostic text only: consumers
                 decide on the reason code of the row. Zero-length if there
                 is no detail."
    ::= { catboyHostReasonEntry 3 }

catboyHostReasonAge OBJECT-TYPE
    SYNTAX      Unsigned32
    UNITS       "seconds"
    MAX-ACCESS  read-only
    STATUS      current
    DESCRIPTION "Seconds since the reason was first seen without a break,
                 from the first-seen time the agent keeps."
    ::= { catboyHostReasonEntry 4 }

-- Conformance

catboyHostGroups      OBJECT IDENTIFIER ::= { catboyHostConformance 1 }
catboyHostCompliances OBJECT IDENTIFIER ::= { catboyHostConformance 2 }

catboyHostCollGroup OBJECT-GROUP
    OBJECTS { catboyHostCollName, catboyHostCollState,
              catboyHostCollLastOkAge, catboyHostCollError }
    STATUS  current
    DESCRIPTION "The collector status table."
    ::= { catboyHostGroups 1 }

catboyHostFirewallGroup OBJECT-GROUP
    OBJECTS { catboyHostFwBackend, catboyHostFwActive, catboyHostFwRules,
              catboyHostFwInputPolicy, catboyHostFwGaps,
              catboyHostFwGapProto, catboyHostFwGapPort,
              catboyHostFwGapProcess }
    STATUS  current
    DESCRIPTION "Firewall backend, state, input policy and the gap table."
    ::= { catboyHostGroups 2 }

catboyHostAptGroup OBJECT-GROUP
    OBJECTS { catboyHostAptUpdateAge, catboyHostAptUpgradable,
              catboyHostAptSecUpgradable, catboyHostUuInstalled,
              catboyHostUuEnabled, catboyHostUuSecurity,
              catboyHostUuLastRunAge, catboyHostUuLastResult,
              catboyHostKernelRunning, catboyHostKernelNewest,
              catboyHostKernelOutdated }
    STATUS  current
    DESCRIPTION "Package updates, unattended-upgrades and kernel versions."
    ::= { catboyHostGroups 3 }

catboyHostRebootGroup OBJECT-GROUP
    OBJECTS { catboyHostRebootRequired, catboyHostRebootPkgs,
              catboyHostUptime }
    STATUS  current
    DESCRIPTION "Reboot-required state and uptime."
    ::= { catboyHostGroups 4 }

catboyHostSysctlGroup OBJECT-GROUP
    OBJECTS { catboyHostSysctlScore, catboyHostSysctlDeviations,
              catboyHostSysctlDevKey, catboyHostSysctlDevExpected,
              catboyHostSysctlDevActual }
    STATUS  deprecated
    DESCRIPTION "sysctl hardening score and the deviation table, first
                 meaning (a value must equal the expected value).
                 Deprecated: replaced by catboyHostSysctlV2Group."
    ::= { catboyHostGroups 5 }

catboyHostJournalGroup OBJECT-GROUP
    OBJECTS { catboyHostJournalCrit1h, catboyHostJournalCrit24h,
              catboyHostJournalCrit48h, catboyHostJournalErr1h,
              catboyHostJournalErr24h, catboyHostJournalErr48h,
              catboyHostJournalOom24h, catboyHostJournalSegv24h,
              catboyHostJournalCore48h, catboyHostKernelTaint,
              catboyHostCritLineAge, catboyHostCritLinePriority,
              catboyHostCritLineIdent, catboyHostCritLineText }
    STATUS  current
    DESCRIPTION "Journal counts, kernel taint and the last crit lines."
    ::= { catboyHostGroups 6 }

catboyHostUnitsGroup OBJECT-GROUP
    OBJECTS { catboyHostUnitsFailed, catboyHostUnitsRestarting,
              catboyHostTimersOverdue, catboyHostFailedName,
              catboyHostFailedAge }
    STATUS  current
    DESCRIPTION "Failed, restarting and overdue systemd units."
    ::= { catboyHostGroups 7 }

catboyHostDnsGroup OBJECT-GROUP
    OBJECTS { catboyHostDnsResolvers, catboyHostDnsFirstIsFleet,
              catboyHostDnsLastMs, catboyHostDnsAvg15mMs,
              catboyHostDnsFail15m }
    STATUS  current
    DESCRIPTION "Resolver configuration and probe results."
    ::= { catboyHostGroups 8 }

catboyHostSshdGroup OBJECT-GROUP
    OBJECTS { catboyHostSshRootLogin, catboyHostSshPasswordAuth,
              catboyHostSshAuthFail24h, catboyHostEmptyPwUsers,
              catboyHostNopasswdSudo, catboyHostWwPathDirs,
              catboyHostSetuidUnpkg }
    STATUS  current
    DESCRIPTION "sshd configuration and local account checks."
    ::= { catboyHostGroups 9 }

catboyHostPressureGroup OBJECT-GROUP
    OBJECTS { catboyHostPsiAvailable, catboyHostPsiCpuSome10,
              catboyHostPsiCpuSome60, catboyHostPsiCpuSome300,
              catboyHostPsiMemSome10, catboyHostPsiMemSome60,
              catboyHostPsiMemSome300, catboyHostPsiMemFull10,
              catboyHostPsiMemFull60, catboyHostPsiMemFull300,
              catboyHostPsiIoSome10, catboyHostPsiIoSome60,
              catboyHostPsiIoSome300, catboyHostPsiIoFull10,
              catboyHostPsiIoFull60, catboyHostPsiIoFull300,
              catboyHostTempMax, catboyHostTempSensors }
    STATUS  current
    DESCRIPTION "Pressure stall information and temperature."
    ::= { catboyHostGroups 10 }

catboyHostDerivedGroup OBJECT-GROUP
    OBJECTS { catboyHostNeedsReboot, catboyHostNeedsRebootAge,
              catboyHostSecPending, catboyHostSecOverdue,
              catboyHostNeedsIntervention, catboyHostSeverity,
              catboyHostHealthScore, catboyHostReasonCount,
              catboyHostReasonSeverity, catboyHostReasonDetail,
              catboyHostReasonAge }
    STATUS  current
    DESCRIPTION "Derived flags, severity, health score and the reason
                 table."
    ::= { catboyHostGroups 11 }

catboyHostCompliance MODULE-COMPLIANCE
    STATUS  deprecated
    DESCRIPTION "Compliance for catboy-agent hosts that run the hostsec
                 collectors. A collector the host does not support still
                 serves its objects with catboyHostCollState unsupported(5)
                 and the unknown values."
    MODULE
        MANDATORY-GROUPS { catboyHostCollGroup, catboyHostFirewallGroup,
                           catboyHostAptGroup, catboyHostRebootGroup,
                           catboyHostSysctlGroup, catboyHostJournalGroup,
                           catboyHostUnitsGroup, catboyHostDnsGroup,
                           catboyHostSshdGroup, catboyHostPressureGroup,
                           catboyHostDerivedGroup }
    ::= { catboyHostCompliances 1 }

catboyHostSysctlV2Group OBJECT-GROUP
    OBJECTS { catboyHostSysctlV2Score, catboyHostSysctlV2Deviations,
              catboyHostSysctlV2DevKey, catboyHostSysctlV2DevExpected,
              catboyHostSysctlV2DevActual }
    STATUS  current
    DESCRIPTION "sysctl hardening score and the deviation table: a value
                 that equals the expected value or is stricter complies."
    ::= { catboyHostGroups 12 }

catboyHostComplianceV2 MODULE-COMPLIANCE
    STATUS  current
    DESCRIPTION "Compliance for catboy-agent hosts that run the hostsec
                 collectors, with the V2 sysctl objects. A collector the
                 host does not support still serves its objects with
                 catboyHostCollState unsupported(5) and the unknown values."
    MODULE
        MANDATORY-GROUPS { catboyHostCollGroup, catboyHostFirewallGroup,
                           catboyHostAptGroup, catboyHostRebootGroup,
                           catboyHostSysctlV2Group, catboyHostJournalGroup,
                           catboyHostUnitsGroup, catboyHostDnsGroup,
                           catboyHostSshdGroup, catboyHostPressureGroup,
                           catboyHostDerivedGroup }
    ::= { catboyHostCompliances 2 }

END
