-- GENERATED by catboy-registry tools/gen.py from templates/snmp/CATBOY-SMI.txt.tmpl - do not edit
CATBOY-SMI DEFINITIONS ::= BEGIN

IMPORTS
    MODULE-IDENTITY, OBJECT-IDENTITY, enterprises
        FROM SNMPv2-SMI;

catboy MODULE-IDENTITY
    LAST-UPDATED "202609250000Z"
    ORGANIZATION "catboy.systems"
    CONTACT-INFO "Marc Schneider, hostmaster@catboy.systems"
    DESCRIPTION  "Structure of management information for the enterprise arc
                 1.3.6.1.4.1.66963. Arc .1 = catboy.systems, .1.4 = SNMP.
                 Each MIB module under catboySnmp follows the SMIv2 layout:
                 notifications under .0, objects under .1, conformance under .2."
    REVISION     "202609250000Z"
    DESCRIPTION  "First version with the assigned enterprise number; module arcs
                 for the agent, PKI, WAF and experimental MIBs."
    ::= { enterprises 66963 }

catboySystems OBJECT-IDENTITY
    STATUS      current
    DESCRIPTION "catboy.systems project arc."
    ::= { catboy 1 }

catboySnmp OBJECT-IDENTITY
    STATUS      current
    DESCRIPTION "Root of all catboy.systems SNMP MIB modules."
    ::= { catboySystems 4 }

catboyAgentSysObjectID OBJECT-IDENTITY
    STATUS      current
    DESCRIPTION "sysObjectID value reported by every host running catboy-agent.
                 It identifies the host as a fleet host only; the host's identity
                 is catboyAgentEnrolmentId in CATBOY-AGENT-MIB."
    ::= { catboySnmp 1 }

-- catboySnmp 2 = CATBOY-AGENT-MIB (catboyAgentMIB)
-- catboySnmp 3 = CATBOY-PKI-MIB (reserved)
-- catboySnmp 4 = CATBOY-WAF-MIB (reserved)

catboyExperimental OBJECT-IDENTITY
    STATUS      current
    DESCRIPTION "Experimental and development MIB objects. Nothing under this arc
                 is stable; an object that becomes stable gets a new number in a
                 module arc and the experimental one is deprecated."
    ::= { catboySnmp 99 }

END
