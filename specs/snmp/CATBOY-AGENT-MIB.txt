-- GENERATED by catboy-registry tools/gen.py from templates/snmp/CATBOY-AGENT-MIB.txt.tmpl - do not edit
CATBOY-AGENT-MIB DEFINITIONS ::= BEGIN

IMPORTS
    MODULE-IDENTITY, OBJECT-TYPE, NOTIFICATION-TYPE, Unsigned32,
    Counter32
        FROM SNMPv2-SMI
    DisplayString, DateAndTime, TruthValue
        FROM SNMPv2-TC
    MODULE-COMPLIANCE, OBJECT-GROUP, NOTIFICATION-GROUP
        FROM SNMPv2-CONF
    catboySnmp
        FROM CATBOY-SMI;

catboyAgentMIB MODULE-IDENTITY
    LAST-UPDATED "202609300000Z"
    ORGANIZATION "catboy.systems"
    CONTACT-INFO "Marc Schneider, hostmaster@catboy.systems"
    DESCRIPTION  "Health and identity of a host running catboy-agent, served by
                 the agent as an AgentX subagent (RFC 2741) of the host's SNMP
                 master agent. Read-only; SNMPv3 authPriv only."
    REVISION     "202609300000Z"
    DESCRIPTION  "Added catboyAgentRelease, catboyAgentBuild,
                 catboyAgentFleetRole, catboyAgentCommandsOk,
                 catboyAgentCommandsFailed, catboyAgentReleaseGroup and
                 catboyAgentComplianceV2."
    REVISION     "202609250000Z"
    DESCRIPTION  "Initial version (rendered from the catboy-registry template)."
    ::= { catboySnmp 2 }

catboyAgentNotifications OBJECT IDENTIFIER ::= { catboyAgentMIB 0 }
catboyAgentObjects       OBJECT IDENTIFIER ::= { catboyAgentMIB 1 }
catboyAgentConformance   OBJECT IDENTIFIER ::= { catboyAgentMIB 2 }

-- Scalars

catboyAgentEnrolmentId OBJECT-TYPE
    SYNTAX      DisplayString (SIZE (0..20))
    MAX-ACCESS  read-only
    STATUS      current
    DESCRIPTION "The catboy-agent enrolment id (agent_id issued by the control
                 plane at enrolment), as decimal digits. The control plane joins
                 an SNMP-discovered host to its configuration item on this value;
                 sysObjectID only says the host is a fleet host. Zero-length
                 while the host is not enrolled."
    ::= { catboyAgentObjects 1 }

catboyAgentEnrolState OBJECT-TYPE
    SYNTAX      INTEGER { unenrolled(1), pending(2), enrolled(3), revoked(4) }
    MAX-ACCESS  read-only
    STATUS      current
    DESCRIPTION "Enrolment state of this host with the fleet control plane."
    ::= { catboyAgentObjects 2 }

catboyAgentVersion OBJECT-TYPE
    SYNTAX      DisplayString (SIZE (0..64))
    MAX-ACCESS  read-only
    STATUS      current
    DESCRIPTION "Installed catboy-agent version."
    ::= { catboyAgentObjects 3 }

catboyAgentLastHeartbeat OBJECT-TYPE
    SYNTAX      DateAndTime
    MAX-ACCESS  read-only
    STATUS      current
    DESCRIPTION "Time of the last successful heartbeat to the control plane,
                 which is also the last successful CatCMDB sync. All eight
                 octets are zero if no heartbeat has succeeded since the agent
                 started."
    ::= { catboyAgentObjects 4 }

catboyAgentTrustAnchor OBJECT-TYPE
    SYNTAX      DisplayString (SIZE (0|64))
    MAX-ACCESS  read-only
    STATUS      current
    DESCRIPTION "SHA-256 fingerprint (lowercase hex) of the root CA installed as
                 trust anchor. Zero-length if none is installed."
    ::= { catboyAgentObjects 5 }

catboyAgentSite OBJECT-TYPE
    SYNTAX      DisplayString (SIZE (0..32))
    MAX-ACCESS  read-only
    STATUS      current
    DESCRIPTION "Site slug the host belongs to. Zero-length if unknown."
    ::= { catboyAgentObjects 6 }

catboyAgentDiskFull OBJECT-TYPE
    SYNTAX      TruthValue
    MAX-ACCESS  read-only
    STATUS      current
    DESCRIPTION "true(1) while any local filesystem the agent watches is above
                 the agent's disk-full threshold, false(2) otherwise. A change
                 of value sends catboyAgentDiskFullNotification."
    ::= { catboyAgentObjects 7 }

catboyAgentBackupFailed OBJECT-TYPE
    SYNTAX      TruthValue
    MAX-ACCESS  read-only
    STATUS      current
    DESCRIPTION "true(1) while the most recent backup of this host failed or is
                 overdue, false(2) otherwise. A change of value sends
                 catboyAgentBackupFailedNotification."
    ::= { catboyAgentObjects 8 }

-- Managed services

catboyAgentServiceTable OBJECT-TYPE
    SYNTAX      SEQUENCE OF CatboyAgentServiceEntry
    MAX-ACCESS  not-accessible
    STATUS      current
    DESCRIPTION "The services catboy-agent manages or watches on this host."
    ::= { catboyAgentObjects 9 }

catboyAgentServiceEntry OBJECT-TYPE
    SYNTAX      CatboyAgentServiceEntry
    MAX-ACCESS  not-accessible
    STATUS      current
    DESCRIPTION "One managed service."
    INDEX       { catboyAgentServiceIndex }
    ::= { catboyAgentServiceTable 1 }

CatboyAgentServiceEntry ::= SEQUENCE {
    catboyAgentServiceIndex      Unsigned32,
    catboyAgentServiceName       DisplayString,
    catboyAgentServiceState      INTEGER,
    catboyAgentServiceLastChange DateAndTime
}

catboyAgentServiceIndex OBJECT-TYPE
    SYNTAX      Unsigned32 (1..2147483647)
    MAX-ACCESS  not-accessible
    STATUS      current
    DESCRIPTION "Row index. Stable for a given service name while the agent
                 runs; may be reassigned after an agent restart. Consumers key
                 on catboyAgentServiceName."
    ::= { catboyAgentServiceEntry 1 }

catboyAgentServiceName OBJECT-TYPE
    SYNTAX      DisplayString (SIZE (1..64))
    MAX-ACCESS  read-only
    STATUS      current
    DESCRIPTION "Service name as known to the host's service manager, for
                 example the systemd unit name."
    ::= { catboyAgentServiceEntry 2 }

catboyAgentServiceState OBJECT-TYPE
    SYNTAX      INTEGER { unknown(1), running(2), stopped(3), failed(4), starting(5) }
    MAX-ACCESS  read-only
    STATUS      current
    DESCRIPTION "Current state of the service."
    ::= { catboyAgentServiceEntry 3 }

catboyAgentServiceLastChange OBJECT-TYPE
    SYNTAX      DateAndTime
    MAX-ACCESS  read-only
    STATUS      current
    DESCRIPTION "Time the service last entered its current state. All eight
                 octets are zero if unknown."
    ::= { catboyAgentServiceEntry 4 }

-- Release and command counters (added 2026-09-30)

catboyAgentRelease OBJECT-TYPE
    SYNTAX      OBJECT IDENTIFIER
    MAX-ACCESS  read-only
    STATUS      current
    DESCRIPTION "The release of the running agent as an OID in the catboy-agent
                 software arc: 1.3.6.1.4.1.66963.1.11.1.1.<major>.<minor>.<patch>
                 (registry specs/software). { 0 0 } if the version is not a
                 plain major.minor.patch."
    ::= { catboyAgentObjects 10 }

catboyAgentBuild OBJECT-TYPE
    SYNTAX      DisplayString (SIZE (0..20))
    MAX-ACCESS  read-only
    STATUS      current
    DESCRIPTION "The build of the running agent: the GitHub Actions run_id of
                 the build workflow, as decimal digits. Its registry build OID is
                 1.3.6.1.4.1.66963.1.11.1.3.<run_id>; it is not served as an
                 OBJECT IDENTIFIER because run_id values exceed the 32-bit
                 sub-identifier limit of SNMP (RFC 2578, 3.5). Zero-length for a
                 build made outside that workflow."
    ::= { catboyAgentObjects 11 }

catboyAgentFleetRole OBJECT-TYPE
    SYNTAX      DisplayString (SIZE (0..64))
    MAX-ACCESS  read-only
    STATUS      current
    DESCRIPTION "The role of this host in the fleet, as configured on the agent
                 (for example hypervisor, dns, ca, waf). Zero-length if not
                 configured."
    ::= { catboyAgentObjects 12 }

catboyAgentCommandsOk OBJECT-TYPE
    SYNTAX      Counter32
    UNITS       "commands"
    MAX-ACCESS  read-only
    STATUS      current
    DESCRIPTION "Commands from the control plane (deploys, updates and the other
                 whitelisted actions) that this agent ran to success. The
                 counter starts at zero when the agent starts; a discontinuity
                 is shown by sysUpTime of the master agent and by
                 catboyAgentLastHeartbeat."
    ::= { catboyAgentObjects 13 }

catboyAgentCommandsFailed OBJECT-TYPE
    SYNTAX      Counter32
    UNITS       "commands"
    MAX-ACCESS  read-only
    STATUS      current
    DESCRIPTION "Commands from the control plane that this agent ran and that
                 failed, or that it refused. The counter starts at zero when the
                 agent starts."
    ::= { catboyAgentObjects 14 }

-- Notifications

catboyAgentDiskFullNotification NOTIFICATION-TYPE
    OBJECTS     { catboyAgentEnrolmentId, catboyAgentDiskFull }
    STATUS      current
    DESCRIPTION "Sent when catboyAgentDiskFull changes value. The varbind value
                 says whether the condition was raised (true) or cleared (false)."
    ::= { catboyAgentNotifications 1 }

catboyAgentBackupFailedNotification NOTIFICATION-TYPE
    OBJECTS     { catboyAgentEnrolmentId, catboyAgentBackupFailed }
    STATUS      current
    DESCRIPTION "Sent when catboyAgentBackupFailed changes value. The varbind
                 value says whether the condition was raised (true) or cleared
                 (false)."
    ::= { catboyAgentNotifications 2 }

-- Conformance

catboyAgentGroups      OBJECT IDENTIFIER ::= { catboyAgentConformance 1 }
catboyAgentCompliances OBJECT IDENTIFIER ::= { catboyAgentConformance 2 }

catboyAgentGroup OBJECT-GROUP
    OBJECTS { catboyAgentEnrolmentId, catboyAgentEnrolState, catboyAgentVersion,
              catboyAgentLastHeartbeat, catboyAgentTrustAnchor, catboyAgentSite,
              catboyAgentDiskFull, catboyAgentBackupFailed }
    STATUS  current
    DESCRIPTION "Scalars every catboy-agent host exposes."
    ::= { catboyAgentGroups 1 }

catboyAgentServiceGroup OBJECT-GROUP
    OBJECTS { catboyAgentServiceName, catboyAgentServiceState,
              catboyAgentServiceLastChange }
    STATUS  current
    DESCRIPTION "The managed-services table."
    ::= { catboyAgentGroups 2 }

catboyAgentNotificationGroup NOTIFICATION-GROUP
    NOTIFICATIONS { catboyAgentDiskFullNotification,
                    catboyAgentBackupFailedNotification }
    STATUS  current
    DESCRIPTION "Disk-full and backup-failed notifications."
    ::= { catboyAgentGroups 3 }

catboyAgentCompliance MODULE-COMPLIANCE
    STATUS  current
    DESCRIPTION "Compliance for catboy-agent hosts."
    MODULE
        MANDATORY-GROUPS { catboyAgentGroup, catboyAgentServiceGroup,
                           catboyAgentNotificationGroup }
    ::= { catboyAgentCompliances 1 }

catboyAgentReleaseGroup OBJECT-GROUP
    OBJECTS { catboyAgentRelease, catboyAgentBuild, catboyAgentFleetRole,
              catboyAgentCommandsOk, catboyAgentCommandsFailed }
    STATUS  current
    DESCRIPTION "Release, build, fleet role and command counters."
    ::= { catboyAgentGroups 4 }

catboyAgentComplianceV2 MODULE-COMPLIANCE
    STATUS  current
    DESCRIPTION "Compliance for catboy-agent hosts from revision 202609300000Z."
    MODULE
        MANDATORY-GROUPS { catboyAgentGroup, catboyAgentServiceGroup,
                           catboyAgentNotificationGroup,
                           catboyAgentReleaseGroup }
    ::= { catboyAgentCompliances 2 }

END
